module latency {
    yang-version 1;
    namespace "urn:opendaylight:params:xml:ns:yang:latency";
    prefix "latency";

    revision "2015-01-05" {
        description "Initial revision of latency model";
    }
    
    typedef latency-type {
    	type enumeration {
    		enum SWITCHES {
    			description "detect latency between switches";
    		}
    	}
    }
    
    rpc network-latency {
    	input {
    		leaf type {
    			type latency-type;
    		}
    	}
    }
    
    rpc switch-switch-latency {
    	input {
    		leaf a-dpId {
    			type uint64;
    		}
    		leaf b-dpId {
    			type uint64;
    		}
    	}
    }
    
}
