module latency-impl {
    yang-version 1;
    namespace "urn:opendaylight:params:xml:ns:yang:latency:impl";
    prefix "latency-impl";

    import config { prefix config; revision-date 2013-04-05; }
    import opendaylight-md-sal-binding { prefix md-sal-binding; revision-date 2013-10-28;}
    import ietf-yang-types {prefix yang; revision-date "2010-09-24";}

    description
        "Service definition for latency project";

    revision "2014-12-10" {
        description
            "Initial revision";
    }

    identity latency {
        base config:module-type;
        config:java-name-prefix Latency;
    }

    augment "/config:modules/config:module/config:configuration" {
        case latency {
            when "/config:modules/config:module/config:type = 'latency'";
            container broker {
                uses config:service-ref {
                    refine type {
                        mandatory true;
                        config:required-identity md-sal-binding:binding-broker-osgi-registry;
                    }
                }
            }
            
            container rpc-registry {
                uses config:service-ref {
                    refine type {
                        mandatory true;
                        config:required-identity md-sal-binding:binding-rpc-registry;
                    }
                }
            }
            
            container notification-service {
                uses config:service-ref {
                    refine type {
                        mandatory true;
                        config:required-identity md-sal-binding:binding-notification-service;
                    }
                }
            }
            
            container data-broker {
                uses config:service-ref {
                    refine type {
                        mandatory false;
                        config:required-identity md-sal-binding:binding-async-data-broker;
                    }
                }
            }
            
            leaf address-destination {
                     type yang:mac-address;
            }     
        }
    }
}
